# anonymous TITLE
anonymous COMMENT

# Specification: Specification 0

## _chap_func: 0 (spec object type     0)
- XHTML attributeDefinition     0: XHTML Value : _attr_heading_text_Spec_object_00000_ 0

### _subchap_user: 2 (spec object type     0)
- XHTML attributeDefinition     0: XHTML Value : _attr_heading_text_Spec_object_00002_ 0

#### _req_func_01: 6 (spec object type     1)
- XHTML attributeDefinition     0: XHTML Value : _attr_reqif_text_Spec_object_00006_ 0

#### _req_func_02: 7 (spec object type     1)
- XHTML attributeDefinition     0: XHTML Value : _attr_reqif_text_Spec_object_00007_ 0

#### _req_func_04: 9 (spec object type     1)
- XHTML attributeDefinition     0: XHTML Value : _attr_reqif_text_Spec_object_00009_ 0

### _subchap_data: 3 (spec object type     0)
- XHTML attributeDefinition     0: XHTML Value : _attr_heading_text_Spec_object_00003_ 0

#### _req_func_03: 8 (spec object type     1)
- XHTML attributeDefinition     0: XHTML Value : _attr_reqif_text_Spec_object_00008_ 0

## _chap_nfunc: 1 (spec object type     0)
- XHTML attributeDefinition     0: XHTML Value : _attr_heading_text_Spec_object_00001_ 0

### _subchap_perf: 4 (spec object type     0)
- XHTML attributeDefinition     0: XHTML Value : _attr_heading_text_Spec_object_00004_ 0

#### _req_nfunc_01: 10 (spec object type     1)
- XHTML attributeDefinition     0: XHTML Value : _attr_reqif_text_Spec_object_00010_ 0

#### _req_nfunc_03: 12 (spec object type     1)
- XHTML attributeDefinition     0: XHTML Value : _attr_reqif_text_Spec_object_00012_ 0

### R6: 5 (spec object type     0)
- XHTML attributeDefinition     0: XHTML Value : _attr_heading_text_Spec_object_00005_ 0

#### _req_nfunc_02: 11 (spec object type     1)
- XHTML attributeDefinition     0: XHTML Value : _attr_reqif_text_Spec_object_00011_ 0

#### _req_nfunc_04: 13 (spec object type     1)
- XHTML attributeDefinition     0: XHTML Value : _attr_reqif_text_Spec_object_00013_ 0
