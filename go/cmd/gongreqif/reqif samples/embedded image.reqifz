A simple ReqIF file with a named specification.

# Specification: Product Requirements Document

## so-1
This is the requirement text, and here is the embedded svg image:
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ANother requirement text, another embedded image, this one is jpg:
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