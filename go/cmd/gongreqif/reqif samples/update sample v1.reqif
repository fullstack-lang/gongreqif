# Typed System Specification v1
Initial version with distinct types for Headings and Requirements.

# Specification: System Specification

## _heading_func: 1. Functional Requirements (Heading)

### _req_func_01 (Requirement)
The system shall allow user registration.

### _req_func_02 (Requirement)
The system shall allow registered users to log in.

### _req_func_03 (Requirement)
The system shall provide a search functionality.

### _req_func_04 (Requirement)
The system shall allow users to reset their password.

## R2: 2. Non-Functional Requirements (Heading)

### _req_nfunc_01 (Requirement)
All pages shall load in under 2 seconds.

### _req_nfunc_02 (Requirement)
The system shall be compatible with modern web browsers.

### _req_nfunc_03 (Requirement)
The system shall have an uptime of 99.9%.

### _req_nfunc_04 (Requirement)
The user interface shall be responsive.
